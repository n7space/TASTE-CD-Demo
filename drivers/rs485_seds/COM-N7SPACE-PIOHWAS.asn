COM-N7SPACE-PIOHWAS DEFINITIONS ::= BEGIN
IMPORTS
DestinationAddress FROM COM-N7SPACE-HWAS
Word FROM COM-N7SPACE-HWAS
WordMask FROM COM-N7SPACE-HWAS
;
PinNumber ::= INTEGER(0 .. 31)
-- Definitions of PIO ports
PioHwas-Port ::= ENUMERATED
{
    pioHwas-Port-A(0),
    pioHwas-Port-B(1),
    pioHwas-Port-C(2),
    pioHwas-Port-D(3),
    pioHwas-Port-E(4)
}
-- I/O line flow direction
PioHwas-Direction ::= ENUMERATED
{
    pioHwas-Direction-Input(0),
    pioHwas-Direction-Output(1)
}
-- Possible I/O line assignment to peripherals.
PioHwas-Control ::= ENUMERATED
{
    pioHwas-Control-Pio(0),
    pioHwas-Control-PeripheralA(1),
    pioHwas-Control-PeripheralB(2),
    pioHwas-Control-PeripheralC(3),
    pioHwas-Control-PeripheralD(4)
}
-- Pio descriptor
PioHwas ::= SEQUENCE 
{ 
    mPortAddress DestinationAddress, 
    mPin Word, 
    mPortPerAddress DestinationAddress, 
    mPortPdrAddress DestinationAddress, 
    mPortOerAddress DestinationAddress, 
    mPortOdrAddress DestinationAddress, 
    mPortIfdrAddress DestinationAddress, 
    mPortSodrAddress DestinationAddress, 
    mPortCodrAddress DestinationAddress, 
    mPortPdsrAddress DestinationAddress, 
    mPortMddrAddress DestinationAddress, 
    mPortPuerAddress DestinationAddress, 
    mPortPudrAddress DestinationAddress, 
    mPortOwerAddress DestinationAddress, 
    mPortOwdrAddress DestinationAddress, 
    mPortIfscdrAddress DestinationAddress, 
    mPortAbcdsr0Address DestinationAddress, 
    mPortAbcdsr1Address DestinationAddress, 
    mPortPpddrAddress DestinationAddress, 
    mPortSchmittAddress DestinationAddress
} 
-- Pin configuration container
PioHwasPinConfig ::= SEQUENCE 
{ 
    mPortConfig PioHwas-Port, 
    mPinConfig PinNumber, 
    mDirectionConfig PioHwas-Direction, 
    mControlConfig PioHwas-Control
} 
-- Pmc descriptor
PmcHwas ::= SEQUENCE 
{ 
    pMC-PCER0-OFFSET DestinationAddress, 
    pMC-PCxR0-PID10-PIOA-MASK WordMask, 
    pMC-PCxR0-PID11-PIOB-MASK WordMask, 
    pMC-PCxR0-PID12-PIOC-MASK WordMask, 
    pMC-PCxR0-PID16-PIOD-MASK WordMask, 
    pMC-PCxR0-PID17-PIOE-MASK WordMask
} 
END
