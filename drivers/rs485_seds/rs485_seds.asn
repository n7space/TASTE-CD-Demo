--  DO NOT EDIT THIS FILE [non user-editable]
RS485-SEDS-DATAVIEW DEFINITIONS ::= BEGIN

    PlatformSpecificPointer ::= INTEGER (0 .. 4294967295) -- 32bit max

    SystemBus ::= INTEGER (0 .. 255)

    SystemDevice ::= INTEGER (0 .. 255)

    RemoteInterface ::= INTEGER (0 .. 255)

    InputDataPtr ::= PlatformSpecificPointer

    DataLength ::= INTEGER (0 .. 4294967295) -- (Broker/Packetizer)const size_t dataSize/Length

    PacketType ::= INTEGER (0 .. 255) -- (Broker/Packetizer)const Packetizer_PacketType packetType

    PacketSource ::= INTEGER (0 .. 65535) -- (Packetizer)const uint16_t source

    PacketDestination ::= INTEGER (0 .. 65535) -- (Packetizer)const uint16_t destination

    PacketPointer ::= PlatformSpecificPointer -- (Packetizer)uint8_t* const packetPointer

    PacketDataOffset ::= INTEGER (0 .. 4294967295) -- (Packetizer)const size_t dataOffset

    RequestErrorCodePtr ::= PlatformSpecificPointer -- (Depacketizer)int32_t* const errorCode

    SystemBusArray ::= SEQUENCE (SIZE (255)) OF SystemBus -- (Broker)enum SystemBus valid_buses[SYSTEM_BUSES_NUMBER]

    InitRequestData ::= SEQUENCE {
        private-data PlatformSpecificPointer, -- (Broker)void* private_data
        bus-id SystemBus, -- (Broker)const enum SystemBus bus_id
        device-id SystemDevice, -- (Broker)const enum SystemDevice device_id
        device-configuration PlatformSpecificPointer, -- (Broker)void* device_configuration
        remote-device-configuration PlatformSpecificPointer -- (Broker)void* remote_device_configuration
    }

    DeliveredRequestData ::= SEQUENCE {
        private-data PlatformSpecificPointer, -- (Broker)void* private_data
        message-data InputDataPtr, -- (Broker)const uint8_t* const
        length DataLength -- (Broker)const size_t
    }

    ReceivedRequestData ::= SEQUENCE {
        private-data PlatformSpecificPointer, -- (Broker)void* private_data
        bus-id SystemBus, -- (Broker)const enum SystemBus bus_id
        message-data InputDataPtr, -- (Broker)const uint8_t* const
        length DataLength -- (Broker)const size_t
    }

END
