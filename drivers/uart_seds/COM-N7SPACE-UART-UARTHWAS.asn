COM-N7SPACE-UART-UARTHWAS DEFINITIONS ::= BEGIN
IMPORTS
Byte FROM COM-N7SPACE-UART-HWAS
DestinationAddress FROM COM-N7SPACE-UART-HWAS
InterruptNumber FROM COM-N7SPACE-UART-HWAS
SourceAddress FROM COM-N7SPACE-UART-HWAS
WordMask FROM COM-N7SPACE-UART-HWAS
;
-- Enum listing Uart instances
UartHwas-Instance ::= ENUMERATED
{
    uart-uartHwas-Instance-0(0),
    uart-uartHwas-Instance-1(1),
    uart-uartHwas-Instance-2(2),
    uart-uartHwas-Instance-3(3),
    uart-uartHwas-Instance-4(4)
}
-- Enum listing supported baudrates
UartHwas-Baudrate ::= ENUMERATED
{
    uart-uartHwas-Baudrate9600(0),
    uart-uartHwas-Baudrate115200(1)
}
-- Uart descriptor
UartHwas ::= SEQUENCE 
{ 
    mInstanceAddress DestinationAddress, 
    mIrqNumber InterruptNumber, 
    mUartCrAddress DestinationAddress, 
    mUartMrAddress DestinationAddress, 
    mUartIerAddress DestinationAddress, 
    mUartIdrAddress DestinationAddress, 
    mUartImrAddress SourceAddress, 
    mUartSrAddress SourceAddress, 
    mUartRhrAddress SourceAddress, 
    mUartThrAddress DestinationAddress, 
    mUartBrgrAddress DestinationAddress
} 
-- Uart configuration container
UartHwasConfig ::= SEQUENCE 
{ 
    mInstance UartHwas-Instance, 
    mBaudrate UartHwas-Baudrate
} 
-- Pmc descriptor
PmcHwasUart ::= SEQUENCE 
{ 
    pMC-PCER0-OFFSET DestinationAddress, 
    pMC-PCER1-OFFSET DestinationAddress, 
    pMC-PCxR0-PID7-UART0-MASK WordMask, 
    pMC-PCxR0-PID8-UART1-MASK WordMask, 
    pMC-PCxR1-PID44-UART2-MASK WordMask, 
    pMC-PCxR1-PID45-UART3-MASK WordMask, 
    pMC-PCxR1-PID46-UART4-MASK WordMask
} 
UartHwasInterfaceType-ReadByteAsyncCmd-Type ::= SEQUENCE 
{ 
    uart UartHwas
} 
UartHwasInterfaceType-ReadByteAsyncCmd-TypeNotify ::= SEQUENCE 
{ 
    byteToRead Byte
} 
UartHwasInterfaceType-SendByteAsyncCmd-Type ::= SEQUENCE 
{ 
    uart UartHwas, 
    byteToSend Byte
} 
UartHwasInterfaceType-SendByteAsyncCmd-TypeNotify ::= SEQUENCE 
{ 
    byteSentFlag Byte
} 
END
