ETD-DEMO-DATAVIEW DEFINITIONS ::=
BEGIN

PhisicValType ::= REAL (-10000.0 .. 10000.0)

SystemMode ::= ENUMERATED { off, idle, on }
DeviceState ::= ENUMERATED { off, on }
Response ::= ENUMERATED { accepted, error }

SystemPhisicAttrs  ::= SEQUENCE {
    velocity  PhisicValType,
    height PhisicValType
}

TC-Mode-Data  ::= SEQUENCE {
    choosen-mode  SystemMode
}

TC-Config-Data  ::= SEQUENCE {
    target-height  PhisicValType
}

TC-Data  ::= CHOICE {
    mode-request TC-Mode-Data,
    config-request TC-Config-Data
}

TM-Data  ::= SEQUENCE {
    mode-confirmation  Response
}

SensorControl-Data  ::= SEQUENCE {
    state-request  DeviceState
}

ActuatorControl-Data  ::= SEQUENCE {
    state-request  DeviceState
}

ActuatorConfig-Data  ::= SEQUENCE {
    target-height PhisicValType
}

SensorStatusUpdate-Data  ::= SEQUENCE {
    device-state  DeviceState,
    system-phisic-attrs SystemPhisicAttrs
}

ActuatorStatusUpdate-Data  ::= SEQUENCE {
    device-state  DeviceState,
    acceleration PhisicValType,
    target-height PhisicValType
}

SystemDataRequest-Data  ::= SEQUENCE {
    actuator-state  DeviceState,
    sensor-state  DeviceState,
    target-height PhisicValType,
    acceleration PhisicValType,
    system-phisic-attrs SystemPhisicAttrs
}

Sense-Data  ::= SEQUENCE {
    phisic-tick  INTEGER (0..4294967296),
    system-phisic-attrs SystemPhisicAttrs,
    control-acceleration PhisicValType
}

DataStream-Data  ::= SEQUENCE {
    phisic-tick  INTEGER (0..4294967296),
    target-height PhisicValType,
    system-phisic-attrs SystemPhisicAttrs,
    control-acceleration PhisicValType
}

END
